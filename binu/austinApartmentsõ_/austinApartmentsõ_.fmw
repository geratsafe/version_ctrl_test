FME workspace austinApartmentsõ_.fmw
Title: City of Austin: Apartments and other (ACAD 2 KML)

Parameters:
- SourceDataset_ACAD = $(FME_MF_DIR)Landmarks.dwg   # Source Autodesk AutoCAD DWG/DXF File(s)

Readers:
- ACAD_1: ACAD from $(SourceDataset_ACAD) in LL84

Writers:
- OGCKML_1: OGCKML to /opt/fmeserver//resources/system/temp/engineresults\austinApartments.kml

Note: Landmarks in Austin, in LL84
Landmarks Point (reader ACAD_1)
    attributes: CFCC char(4), FILE number(6,0), LALAT number(9,0), LALONG number(10,0), LANAME char(31), LAND number(4,0), MODULE char(9), OBJECTID number(5,0), SOURCE char(2)
    -> TestFilter
Note: Copy LANAME to kml_name / (legend entry and label)
AttributeCopier_kml_name
    ATTR_LIST = kml_name,LANAME
    -> NewFeatureType (writer OGCKML_1)
Note: Fanout by category to / produce folders in KML file
NewFeatureType (writer OGCKML_1)

Bookmark: Find landmark type
TestFilter
    DEFAULT_VALUE = <UNFILTERED>
    TEST_LIST:
      BOOL_OP,OR,COMPOSITE_TEST,<Unused>,TEST_CLAUSE,"TEST @Value(LANAME) CONTAINS apartment
      TEST @Value(LANAME) CONTAINS townhome",Apartments,BOOL_OP,OR,COMPOSITE_TEST,<Unused>,TEST_CLAUSE,"TEST @Value(LANAME) CONTAINS school",School,BOOL_OP,OR,COMPOSITE_TEST,<Unused>,TEST_CLAUSE,"TEST @Value(LANAME) CONTAINS shop
      TEST @Value(LANAME) CONTAINS mall",Shopping,BOOL_OP,OR,COMPOSITE_TEST,<Unused>,TEST_CLAUSE,"TEST @Value(LANAME) CONTAINS airport
      TEST @Value(LANAME) CONTAINS international",Airports
    Apartments -> AttributeCreator_Apartments
    School -> AttributeCreator_School
    Shopping -> AttributeCreator_Shopping
    Airports -> AttributeCreator_Airports

Bookmark: Category for fanout
  Create the category attribute for
   feature type fanout.
AttributeCreator_Apartments
    ATTR_LIST = category,Apartments
    -> KMLStyler_apartments
AttributeCreator_School
    ATTR_LIST = category,School
    -> KMLStyler_school
AttributeCreator_Shopping
    ATTR_LIST = category,Shopping
    -> KMLStyler_shopping
AttributeCreator_Airports
    ATTR_LIST = category,Airports
    -> KMLStyler_airports

Bookmark: Apply KML Style
KMLStyler_apartments
    FILL_OPACITY = 0.4
    ICON_NAME = I1
    ICON_OPACITY = 1.0
    ICON_SCALE = 0.7
    LABEL_OPACITY = 1.0
    LABEL_SCALE = 0.8
    LABEL_VISIBILITY = Yes
    LINE_WIDTH = 1.0
    LINE_WIDTH_UNITS = Pixels (Display Units)
    OPACITY = 1.0
    STYLE_PER_FEATURE = Yes
    KMLStyled -> AttributeCopier_kml_name
KMLStyler_school
    FILL_OPACITY = 0.4
    ICON_NAME = B2
    ICON_OPACITY = 1.0
    ICON_SCALE = 0.3
    LABEL_OPACITY = 1.0
    LABEL_SCALE = 0.6
    LABEL_VISIBILITY = Yes
    LINE_WIDTH = 1.0
    LINE_WIDTH_UNITS = Pixels (Display Units)
    OPACITY = 1.0
    STYLE_PER_FEATURE = Yes
    KMLStyled -> AttributeCopier_kml_name
KMLStyler_shopping
    FILL_OPACITY = 0.4
    ICON_NAME = D2
    ICON_OPACITY = 1.0
    ICON_SCALE = 0.3
    LABEL_OPACITY = 1.0
    LABEL_SCALE = 0.6
    LABEL_VISIBILITY = Yes
    LINE_WIDTH = 1.0
    LINE_WIDTH_UNITS = Pixels (Display Units)
    OPACITY = 1.0
    STYLE_PER_FEATURE = Yes
    KMLStyled -> AttributeCopier_kml_name
KMLStyler_airports
    FILL_OPACITY = 0.4
    ICON_NAME = M4
    ICON_OPACITY = 1.0
    ICON_SCALE = 0.6
    LABEL_OPACITY = 1.0
    LABEL_SCALE = 0.6
    LABEL_VISIBILITY = Yes
    LINE_WIDTH = 1.0
    LINE_WIDTH_UNITS = Pixels (Display Units)
    OPACITY = 1.0
    STYLE_PER_FEATURE = Yes
    KMLStyled -> AttributeCopier_kml_name
