FME workspace backupConfiguration_vctrl.fmw
Shutdown Python:
      from pyfme import *
      import os, datetime

      backupDestination = FME_MacroValues["BACKUP_DESTINATION"]
      appendDate = FME_MacroValues["BACKUP_APPEND_DATE"]

      if (appendDate == "Yes") :
          newDest = backupDestination.rstrip(".fsconfig") + ("_%s.fsconfig" % datetime.datetime.now().strftime("%d-%m-%y_%H-%M-%S"))
          os.rename(backupDestination, newDest)

Parameters:
- BACKUP_APPEND_DATE = Yes   # Append Date
- SERVER_USERNAME =   # Server Username
- SERVER_PASSWORD =   # Server Password
- BACKUP_DESTINATION = $(FME_SHAREDRESOURCE_BACKUP)ServerConfigPackage.fsconfig   # Backup Destination

Creator
    NUM = 1
    GEOMTYPE = Geometry Object
    CREATED -> HTTPCaller
HTTPCaller
    TARGET_URL = $(FME_SERVER_WEB_URL)/fmerest/v3/migration/backup/download
    USE_COOKIES = No
    FILE_PATH_ATTR = _response_file_path
    TRANSFER_TIMEOUT_LENGTH = 0
    RESPONSE_HEADER_LIST_ATTR = _headers
    FOLLOW_REDIRECTS = No
    STATUS_CODE_ATTR = _http_status_code
    AUTH_PASSWORD = $(SERVER_PASSWORD)
    UPLOAD_CONTENT_TYPE = URL Encoded (application/x-www-form-urlencoded)
    AUTH_USERNAME = $(SERVER_USERNAME)
    CONNECTION_TIMEOUT_LENGTH = 0
    HTTP_METHOD = POST
    SAVE_MULTI = No
    ERROR_ATTR = _error
    OUTPUT_FILENAME = $(BACKUP_DESTINATION)
    VERIFY_SSL_CERTIFICATES = No
    AUTH_METHOD = Basic
    SAVE_FILE = File
    UPLOAD_BODY = exportPackageName=ServerConfigPackage.fsconfig
    UPLOAD_TYPE = Specify Upload Body
    <Rejected> -> Logger
Logger
    MAXFEATS = 20
    MAXCOORDS = 20
    LOG_FEATURE = LOG_ONLY
    MESSAGE = Feature is:
    SEVERITY = INFO
    LOGGED -> Terminator
Terminator
    MESSAGE = Unable to retrieve backup from FME Server `$(FME_SERVER_WEB_URL)'. Please ensure that the credential are correct and that user `$(SERVER_USERNAME)' has fmesuperuser role. The error was: @Value(_error).
